--
-- Copyright (c) 2004-2024, Infoblox, Inc
-- All rights reserved.

IB-PLATFORMONE-MIB DEFINITIONS ::= BEGIN

IMPORTS
   OBJECT-TYPE, NOTIFICATION-TYPE, MODULE-IDENTITY, enterprises
        FROM SNMPv2-SMI
   TEXTUAL-CONVENTION FROM SNMPv2-TC
   Counter FROM RFC1155-SMI
   ibPlatformOne, IbString, IbIpAddr, IbFloat FROM IB-SMI-MIB;

ibPlatformModule MODULE-IDENTITY
    LAST-UPDATED "202209120000Z"  -- September 12, 2022
    ORGANIZATION "Infoblox"
    CONTACT-INFO "Please See IB-SMI-MIB."
    DESCRIPTION "This file defines the Infoblox One platform MIB."

    REVISION  "202209120000Z"  -- September 12, 2022
    DESCRIPTION "Added continuous serial numbers in the services as bloxtools service was removed"

    REVISION  "202112160000Z"  -- December 16, 2021
    DESCRIPTION "Remove bloxtools services"

    REVISION  "201806120000Z"  -- Jun 12, 2018
    DESCRIPTION "Remove the TEXTUAL-CONVENTION IbSnicCoreNames for IbString type"

    REVISION  "201803260000Z"  -- Mar 26, 2018
    DESCRIPTION "Add SNIC CPU Core utilization for the cores"

    REVISION  "201606120000Z"  -- Jun 12, 2016
    DESCRIPTION "Add BFD service status"

    REVISION  "201606070000Z"  -- June 07, 2016
    DESCRIPTION "Add Outbound traps"

    REVISION  "201605060000Z"  -- May 06, 2016
    DESCRIPTION "Removed ibCPUTemperature OBJECT-TYPE"

    REVISION  "201511190000Z"  -- November 19, 2015
    DESCRIPTION "Add SNIC interface statistics"

    REVISION  "201510290000Z"  -- Oct 29, 2015
    DESCRIPTION "Add Taxii service status"

    REVISION  "201510090000Z"  -- Oct 9, 2015
    DESCRIPTION "Add Analytics service status"

    REVISION  "201505190000Z"  -- May 19, 2015
    DESCRIPTION "Add new float OIDs for CPU temprature"

    REVISION  "201407300000Z"  -- July 30, 2014
    DESCRIPTION "Add Cloud API service status"

    REVISION  "201310290000Z"  -- October 29, 2013
    DESCRIPTION "Add Threat Protection service status info"

    REVISION  "201310220000Z"  -- October 22, 2013
    DESCRIPTION "Add Discovery Capacity info"

    REVISION  "201308020000Z"  -- August 02, 2013
    DESCRIPTION "Add Swap Usage info"

    REVISION  "201305070000Z"  --  May 07, 2013
    DESCRIPTION   "Added Discovery status services"

    REVISION  "201205240000Z"  --  May 24, 2012
    DESCRIPTION   "Rename Node1, Node2 to Node, PassiveNode"
    
    REVISION  "201204130000Z"  --  April 13, 2012
    DESCRIPTION   "Added DNS Cache Acceleration info"
    
    REVISION  "201112020000Z"  --  December 02, 2011
    DESCRIPTION   "Add support for 8 fans and 8 raid disks"
    
    REVISION  "201112010000Z"  --  December 01, 2011
    DESCRIPTION   "Added second power-supply service"

    REVISION  "201105050000Z"  --  May 05, 2011
    DESCRIPTION   "Removed Radius service status info"

    REVISION  "201010190000Z"  --  October 19, 2010
    DESCRIPTION   "Added BGP service status info"

    REVISION  "201007280000Z"  --  July 28, 2010
    DESCRIPTION   "Added MIBs for Node status info"

    REVISION  "200906050000Z"  --  June 05, 2009
    DESCRIPTION   "Added MIBs for CPU, Memory usage"

    REVISION  "200809290000Z"  --  Sep 29, 2008
    DESCRIPTION   "Added security counters"

    REVISION  "200501100000Z"  --  Jan 10, 2005
    DESCRIPTION   "Added copyright"

    REVISION  "200405210000Z"  --  May 21, 2004
    DESCRIPTION   "Creation of the MIB file"

    ::= { ibPlatformOne 1 }

-- PlatformOne Mib Definitions


ibClusterReplicationStatusTable OBJECT-TYPE
   SYNTAX SEQUENCE OF IbClusterReplicationStatusEntry
   MAX-ACCESS    not-accessible
   STATUS        current
   DESCRIPTION   "A table of Physical Node's Grid Replication Status."
   ::= { ibPlatformModule 2 }

ibClusterReplicationStatusEntry OBJECT-TYPE
   SYNTAX        IbClusterReplicationStatusEntry
   MAX-ACCESS    not-accessible
   STATUS        current
   DESCRIPTION   "A conceptual row containing info about a particular
                  grid replication status."
   INDEX         {ibNodeIPAddress}
   ::= { ibClusterReplicationStatusTable 1 }

IbClusterReplicationStatusEntry ::=
   SEQUENCE {
     ibNodeIPAddress     	  IbIpAddr,
     ibNodeReplicationStatus	  IbString,
     ibNodeQueueFromMaster        INTEGER,
     ibNodeLastRepTimeFromMaster  IbString,
     ibNodeQueueToMaster          INTEGER,
     ibNodeLastRepTimeToMaster	  IbString
   }

ibNodeIPAddress OBJECT-TYPE
   SYNTAX        IbIpAddr
   MAX-ACCESS    read-only
   STATUS        current
   DESCRIPTION   "Physical node IP address."
   ::= { ibClusterReplicationStatusEntry 1 }

ibNodeReplicationStatus OBJECT-TYPE
   SYNTAX        IbString
   MAX-ACCESS    read-only
   STATUS        current
   DESCRIPTION   "Replication queue status for this node."
   ::= { ibClusterReplicationStatusEntry 2 }

ibNodeQueueFromMaster OBJECT-TYPE
   SYNTAX        INTEGER
   MAX-ACCESS    read-only
   STATUS        current
   DESCRIPTION   "Sent queue size from master."
   ::= { ibClusterReplicationStatusEntry 3 }

ibNodeLastRepTimeFromMaster OBJECT-TYPE
   SYNTAX        IbString
   MAX-ACCESS    read-only
   STATUS        current
   DESCRIPTION   "Last sent time from master."
   ::= { ibClusterReplicationStatusEntry 4 }

ibNodeQueueToMaster OBJECT-TYPE
   SYNTAX        INTEGER
   MAX-ACCESS    read-only
   STATUS        current
   DESCRIPTION   "Receive queue size to master."
   ::= { ibClusterReplicationStatusEntry 5 }

ibNodeLastRepTimeToMaster OBJECT-TYPE
   SYNTAX        IbString
   MAX-ACCESS    read-only
   STATUS        current
   DESCRIPTION   "Last receive time to master."
   ::= { ibClusterReplicationStatusEntry 6 }

ibNetworkMonitor OBJECT IDENTIFIER
   ::= { ibPlatformModule 3 }

ibHardwareType  OBJECT-TYPE
   SYNTAX         IbString
   MAX-ACCESS     read-only
   STATUS         current
   DESCRIPTION "Infoblox One hardware type"
   ::= { ibPlatformModule 4 }

ibHardwareId  OBJECT-TYPE
   SYNTAX         IbString
   MAX-ACCESS     read-only
   STATUS         current
   DESCRIPTION "Infoblox One hardware id"
   ::= { ibPlatformModule 5 }

ibSerialNumber  OBJECT-TYPE
   SYNTAX         IbString
   MAX-ACCESS     read-only
   STATUS         current
   DESCRIPTION "Infoblox One device serial number"
   ::= { ibPlatformModule 6 }

ibNiosVersion  OBJECT-TYPE
   SYNTAX         IbString
   MAX-ACCESS     read-only
   STATUS         current
   DESCRIPTION "Infoblox One NIOS version"
   ::= { ibPlatformModule 7 }

ibSystemMonitor  OBJECT IDENTIFIER
   ::= { ibPlatformModule 8 }

ibSystemMonitorCpu  OBJECT IDENTIFIER
   ::= { ibSystemMonitor 1 }

ibSystemMonitorMem  OBJECT IDENTIFIER
   ::= { ibSystemMonitor 2 }

ibSystemMonitorSwap  OBJECT IDENTIFIER
   ::= { ibSystemMonitor 3 }

ibSystemMonitorSnic  OBJECT IDENTIFIER
   ::= { ibSystemMonitor 4 }

ibSystemMonitorCpuUsage  OBJECT-TYPE
   SYNTAX         INTEGER
   MAX-ACCESS     read-only
   STATUS         current
   DESCRIPTION "Current average CPU usage"
   ::= { ibSystemMonitorCpu 1 }

ibSystemMonitorMemUsage  OBJECT-TYPE
   SYNTAX         INTEGER
   MAX-ACCESS     read-only
   STATUS         current
   DESCRIPTION "Current Memory usage"
   ::= { ibSystemMonitorMem 1 }

ibSystemMonitorSwapUsage  OBJECT-TYPE
   SYNTAX         INTEGER
   MAX-ACCESS     read-only
   STATUS         current
   DESCRIPTION "Current Swap usage"
   ::= { ibSystemMonitorSwap 1 }

ibNetworkMonitorDNS  OBJECT IDENTIFIER
   ::= { ibNetworkMonitor 1 }

ibNetworkMonitorDNSActive OBJECT-TYPE
   SYNTAX	INTEGER { nonactive(0), active(1) }
   MAX-ACCESS	read-only
   STATUS	current
   DESCRIPTION	"Equal to 1 if monitoring is active. No other data is
		likely to be correct if not active"
   ::= { ibNetworkMonitorDNS 1 }

ibNetworkMonitorDNSNonAA OBJECT IDENTIFIER
   ::= { ibNetworkMonitorDNS 2 }

ibNetworkMonitorDNSNonAAT1 OBJECT IDENTIFIER
   ::= { ibNetworkMonitorDNSNonAA 1 }

ibNetworkMonitorDNSNonAAT5 OBJECT IDENTIFIER
   ::= { ibNetworkMonitorDNSNonAA 2 }

ibNetworkMonitorDNSNonAAT15 OBJECT IDENTIFIER
   ::= { ibNetworkMonitorDNSNonAA 3 }

ibNetworkMonitorDNSNonAAT60 OBJECT IDENTIFIER
   ::= { ibNetworkMonitorDNSNonAA 4 }

ibNetworkMonitorDNSNonAAT1440 OBJECT IDENTIFIER
   ::= { ibNetworkMonitorDNSNonAA 5 }

ibNetworkMonitorDNSAA OBJECT IDENTIFIER
   ::= { ibNetworkMonitorDNS 3 }

ibNetworkMonitorDNSAAT1 OBJECT IDENTIFIER
   ::= { ibNetworkMonitorDNSAA 1 }

ibNetworkMonitorDNSAAT5 OBJECT IDENTIFIER
   ::= { ibNetworkMonitorDNSAA 2 }

ibNetworkMonitorDNSAAT15 OBJECT IDENTIFIER
   ::= { ibNetworkMonitorDNSAA 3 }

ibNetworkMonitorDNSAAT60 OBJECT IDENTIFIER
   ::= { ibNetworkMonitorDNSAA 4 }

ibNetworkMonitorDNSAAT1440 OBJECT IDENTIFIER
   ::= { ibNetworkMonitorDNSAA 5 }

ibNetworkMonitorDNSNonAAT1AvgLatency OBJECT-TYPE
   SYNTAX	INTEGER
   MAX-ACCESS	read-only
   STATUS	current
   DESCRIPTION	"Average Latencies (in microseconds) for incoming DNS
		 queries during the last 1 minute where the reply was
		 non authoritative"
   ::= { ibNetworkMonitorDNSNonAAT1 1 }

ibNetworkMonitorDNSNonAAT1Count OBJECT-TYPE
   SYNTAX	INTEGER
   MAX-ACCESS	read-only
   STATUS	current
   DESCRIPTION	"Number of queries used to calculate the average latencies
		 during the last 1 minute where the reply was non
		 authoritative"
   ::= { ibNetworkMonitorDNSNonAAT1 2 }

ibNetworkMonitorDNSNonAAT5AvgLatency OBJECT-TYPE
   SYNTAX	INTEGER
   MAX-ACCESS	read-only
   STATUS	current
   DESCRIPTION	"Average Latencies (in microseconds) for incoming DNS
		 queries during the last 5 minutes where the reply was
		 non authoritative"
   ::= { ibNetworkMonitorDNSNonAAT5 1 }

ibNetworkMonitorDNSNonAAT5Count OBJECT-TYPE
   SYNTAX	INTEGER
   MAX-ACCESS	read-only
   STATUS	current
   DESCRIPTION	"Number of queries used to calculate the average latencies
		 during the last 5 minutes where the reply was non
		 authoritative"
   ::= { ibNetworkMonitorDNSNonAAT5 2 }

ibNetworkMonitorDNSNonAAT15AvgLatency OBJECT-TYPE
   SYNTAX	INTEGER
   MAX-ACCESS	read-only
   STATUS	current
   DESCRIPTION	"Average Latencies (in microseconds) for incoming DNS
		 queries during the last 15 minutes where the reply was
		 non authoritative"
   ::= { ibNetworkMonitorDNSNonAAT15 1 }

ibNetworkMonitorDNSNonAAT15Count OBJECT-TYPE
   SYNTAX	INTEGER
   MAX-ACCESS	read-only
   STATUS	current
   DESCRIPTION	"Number of queries used to calculate the average latencies
		 during the last 15 minutes where the reply was non
		 authoritative"
   ::= { ibNetworkMonitorDNSNonAAT15 2 }

ibNetworkMonitorDNSNonAAT60AvgLatency OBJECT-TYPE
   SYNTAX	INTEGER
   MAX-ACCESS	read-only
   STATUS	current
   DESCRIPTION	"Average Latencies (in microseconds) for incoming DNS
		 queries during the last 60 minutes where the reply was
		 non authoritative"
   ::= { ibNetworkMonitorDNSNonAAT60 1 }

ibNetworkMonitorDNSNonAAT60Count OBJECT-TYPE
   SYNTAX	INTEGER
   MAX-ACCESS	read-only
   STATUS	current
   DESCRIPTION	"Number of queries used to calculate the average latencies
		 during the last 60 minutes where the reply was non
		 authoritative"
   ::= { ibNetworkMonitorDNSNonAAT60 2 }

ibNetworkMonitorDNSNonAAT1440AvgLatency OBJECT-TYPE
   SYNTAX	INTEGER
   MAX-ACCESS	read-only
   STATUS	current
   DESCRIPTION	"Average Latencies (in microseconds) for incoming DNS
		 queries during the last 1440 minutes (24 hours) where
		 the reply was non authoritative"
   ::= { ibNetworkMonitorDNSNonAAT1440 1 }

ibNetworkMonitorDNSNonAAT1440Count OBJECT-TYPE
   SYNTAX	INTEGER
   MAX-ACCESS	read-only
   STATUS	current
   DESCRIPTION	"Number of queries used to calculate the average latencies
		 during the last 1440 minutes (24 hours) where the
		 reply was non authoritative"
   ::= { ibNetworkMonitorDNSNonAAT1440 2 }

ibNetworkMonitorDNSAAT1AvgLatency OBJECT-TYPE
   SYNTAX	INTEGER
   MAX-ACCESS	read-only
   STATUS	current
   DESCRIPTION	"Average Latencies (in microseconds) for incoming DNS
		 queries during the last 1 minute where the reply was
		 authoritative"
   ::= { ibNetworkMonitorDNSAAT1 1 }

ibNetworkMonitorDNSAAT1Count OBJECT-TYPE
   SYNTAX	INTEGER
   MAX-ACCESS	read-only
   STATUS	current
   DESCRIPTION	"Number of queries used to calculate the average latencies
		 during the last 1 minute where the reply was
		 authoritative"
   ::= { ibNetworkMonitorDNSAAT1 2 }

ibNetworkMonitorDNSAAT5AvgLatency OBJECT-TYPE
   SYNTAX	INTEGER
   MAX-ACCESS	read-only
   STATUS	current
   DESCRIPTION	"Average Latencies (in microseconds) for incoming DNS
		 queries during the last 5 minutes where the reply was
		 authoritative"
   ::= { ibNetworkMonitorDNSAAT5 1 }

ibNetworkMonitorDNSAAT5Count OBJECT-TYPE
   SYNTAX	INTEGER
   MAX-ACCESS	read-only
   STATUS	current
   DESCRIPTION	"Number of queries used to calculate the average latencies
		 during the last 5 minutes where the reply was
		 authoritative"
   ::= { ibNetworkMonitorDNSAAT5 2 }

ibNetworkMonitorDNSAAT15AvgLatency OBJECT-TYPE
   SYNTAX	INTEGER
   MAX-ACCESS	read-only
   STATUS	current
   DESCRIPTION	"Average Latencies (in microseconds) for incoming DNS
		 queries during the last 15 minutes where the reply was
		 authoritative"
   ::= { ibNetworkMonitorDNSAAT15 1 }

ibNetworkMonitorDNSAAT15Count OBJECT-TYPE
   SYNTAX	INTEGER
   MAX-ACCESS	read-only
   STATUS	current
   DESCRIPTION	"Number of queries used to calculate the average latencies
		 during the last 15 minutes where the reply was
		 authoritative"
   ::= { ibNetworkMonitorDNSAAT15 2 }

ibNetworkMonitorDNSAAT60AvgLatency OBJECT-TYPE
   SYNTAX	INTEGER
   MAX-ACCESS	read-only
   STATUS	current
   DESCRIPTION	"Average Latencies (in microseconds) for incoming DNS
		 queries during the last 60 minutes where the reply was
		 authoritative"
   ::= { ibNetworkMonitorDNSAAT60 1 }

ibNetworkMonitorDNSAAT60Count OBJECT-TYPE
   SYNTAX	INTEGER
   MAX-ACCESS	read-only
   STATUS	current
   DESCRIPTION	"Number of queries used to calculate the average latencies
		 during the last 60 minutes where the reply was
		 authoritative"
   ::= { ibNetworkMonitorDNSAAT60 2 }

ibNetworkMonitorDNSAAT1440AvgLatency OBJECT-TYPE
   SYNTAX	INTEGER
   MAX-ACCESS	read-only
   STATUS	current
   DESCRIPTION	"Average Latencies (in microseconds) for incoming DNS
		 queries during the last 1440 minutes (24 hours) where
		 the reply was authoritative"
   ::= { ibNetworkMonitorDNSAAT1440 1 }

ibNetworkMonitorDNSAAT1440Count OBJECT-TYPE
   SYNTAX	INTEGER
   MAX-ACCESS	read-only
   STATUS	current
   DESCRIPTION	"Number of queries used to calculate the average latencies
		 during the last 1440 minutes (24 hours) where the reply was
		 authoritative"
   ::= { ibNetworkMonitorDNSAAT1440 2 }

ibNetworkMonitorDNSSecurity OBJECT IDENTIFIER
   ::= { ibNetworkMonitorDNS 4 }

ibNetworkMonitorDNSSecurityInvalidPort OBJECT IDENTIFIER
   ::= { ibNetworkMonitorDNSSecurity 1 }

ibNetworkMonitorDNSSecurityInvalidPort1 OBJECT-TYPE
   SYNTAX       INTEGER
   MAX-ACCESS   read-only
   STATUS       current
   DESCRIPTION  "Number of DNS responses to invalid ports
                during the last 1 minute"
   ::= { ibNetworkMonitorDNSSecurityInvalidPort 1 }

ibNetworkMonitorDNSSecurityInvalidPort5 OBJECT-TYPE
   SYNTAX       INTEGER
   MAX-ACCESS   read-only
   STATUS       current
   DESCRIPTION  "Number of DNS responses to invalid ports
                during the last 5 minutes"
   ::= { ibNetworkMonitorDNSSecurityInvalidPort 2 }

ibNetworkMonitorDNSSecurityInvalidPort15 OBJECT-TYPE
   SYNTAX       INTEGER
   MAX-ACCESS   read-only
   STATUS       current
   DESCRIPTION  "Number of DNS responses to invalid ports
                during the last 15 minutes"
   ::= { ibNetworkMonitorDNSSecurityInvalidPort 3 }

ibNetworkMonitorDNSSecurityInvalidPort60 OBJECT-TYPE
   SYNTAX       INTEGER
   MAX-ACCESS   read-only
   STATUS       current
   DESCRIPTION  "Number of DNS responses to invalid ports
                during the last 60 minutes"
   ::= { ibNetworkMonitorDNSSecurityInvalidPort 4 }

ibNetworkMonitorDNSSecurityInvalidPort1440 OBJECT-TYPE
   SYNTAX       INTEGER
   MAX-ACCESS   read-only
   STATUS       current
   DESCRIPTION  "Number of DNS responses to invalid ports
                during the last 1440 minutes (24 hours)"
   ::= { ibNetworkMonitorDNSSecurityInvalidPort 5 }

ibNetworkMonitorDNSSecurityInvalidPortCount OBJECT-TYPE
   SYNTAX       Counter
   MAX-ACCESS   read-only
   STATUS       current
   DESCRIPTION  "Number of DNS responses to invalid ports"
   ::= { ibNetworkMonitorDNSSecurityInvalidPort 6 }

ibNetworkMonitorDNSSecurityInvalidTxid OBJECT IDENTIFIER
   ::= { ibNetworkMonitorDNSSecurity 2 }

ibNetworkMonitorDNSSecurityInvalidTxid1 OBJECT-TYPE
   SYNTAX       INTEGER
   MAX-ACCESS   read-only
   STATUS       current
   DESCRIPTION  "Number of DNS responses with an invalid TXID
                during the last 1 minute"
   ::= { ibNetworkMonitorDNSSecurityInvalidTxid 1 }

ibNetworkMonitorDNSSecurityInvalidTxid5 OBJECT-TYPE
   SYNTAX       INTEGER
   MAX-ACCESS   read-only
   STATUS       current
   DESCRIPTION  "Number of DNS responses with an invalid TXID
                during the last 5 minutes"
   ::= { ibNetworkMonitorDNSSecurityInvalidTxid 2 }

ibNetworkMonitorDNSSecurityInvalidTxid15 OBJECT-TYPE
   SYNTAX       INTEGER
   MAX-ACCESS   read-only
   STATUS       current
   DESCRIPTION  "Number of DNS responses with an invalid TXID
                during the last 15 minutes"
   ::= { ibNetworkMonitorDNSSecurityInvalidTxid 3 }

ibNetworkMonitorDNSSecurityInvalidTxid60 OBJECT-TYPE
   SYNTAX       INTEGER
   MAX-ACCESS   read-only
   STATUS       current
   DESCRIPTION  "Number of DNS responses with an invalid TXID
                during the last 60 minutes"
   ::= { ibNetworkMonitorDNSSecurityInvalidTxid 4 }

ibNetworkMonitorDNSSecurityInvalidTxid1440 OBJECT-TYPE
   SYNTAX       INTEGER
   MAX-ACCESS   read-only
   STATUS       current
   DESCRIPTION  "Number of DNS responses with an invalid TXID
                during the last 1440 minutes (24 hours)"
   ::= { ibNetworkMonitorDNSSecurityInvalidTxid 5 }

ibNetworkMonitorDNSSecurityInvalidTxidCount OBJECT-TYPE
   SYNTAX       Counter
   MAX-ACCESS   read-only
   STATUS       current
   DESCRIPTION  "Number of DNS responses with an invalid TXID"
   ::= { ibNetworkMonitorDNSSecurityInvalidTxid 6 }

ibNetworkMonitorDNSSecurityInvalidPortOnly OBJECT-TYPE
   SYNTAX       Counter
   MAX-ACCESS   read-only
   STATUS       current
   DESCRIPTION  "Number of DNS responses to invalid ports
                with a valid TXID"
   ::= { ibNetworkMonitorDNSSecurity 3 }

ibNetworkMonitorDNSSecurityInvalidTxidOnly OBJECT-TYPE
   SYNTAX       Counter
   MAX-ACCESS   read-only
   STATUS       current
   DESCRIPTION  "Number of DNS responses to valid ports
                with an invalid TXID"
   ::= { ibNetworkMonitorDNSSecurity 4 }

ibNetworkMonitorDNSSecurityInvalidTxidAndPort OBJECT-TYPE
   SYNTAX       Counter
   MAX-ACCESS   read-only
   STATUS       current
   DESCRIPTION  "Number of DNS responses to an invalid port
                and with an invalid TXID"
   ::= { ibNetworkMonitorDNSSecurity 5 }

IbServiceStates ::= TEXTUAL-CONVENTION
   STATUS        current
   DESCRIPTION   "It defines the states for infoblox services
                  Note: NTP service will always be running on NIOS,
                  even when disabled in the GUI.This is for internal
                  grid operations."
   SYNTAX        INTEGER {
                   working      (1),
                   warning      (2),
                   failed       (3),
                   inactive     (4),
                   unknown      (5)
                 }

IbServiceNames ::= TEXTUAL-CONVENTION
   STATUS        current
   DESCRIPTION   "It defines the names for infoblox services."
   SYNTAX        INTEGER {
                   dhcp             (1),
                   dns              (2),
                   ntp              (3),
                   tftp             (4),
                   http-file-dist   (5),
                   ftp              (6),
                   node-status      (7),
                   disk-usage       (8),
                   enet-lan         (9),
                   enet-lan2        (10),
                   enet-ha          (11),
                   enet-mgmt        (12),
-- commenting this out, NIOS-77796   lcd              (13),
                   memory           (14),
                   replication      (15),
                   db-object        (16),
                   raid-summary     (17),
                   raid-disk1       (18),
                   raid-disk2       (19),
                   raid-disk3       (20),
                   raid-disk4       (21),
                   raid-disk5       (22),
                   raid-disk6       (23),
                   raid-disk7       (24),
                   raid-disk8       (25),
                   fan1             (26),
                   fan2             (27),
                   fan3             (28),
                   fan4             (29),
                   fan5             (30),
                   fan6             (31),
                   fan7             (32),
                   fan8             (33),
                   power-supply1    (34),
                   power-supply2    (35),
                   ntp-sync         (36),
                   cpu1-temp        (37),
                   cpu2-temp        (38),
                   sys-temp         (39),
                   raid-battery     (40),
                   cpu-usage        (41),
                   ospf             (42),
                   bgp              (43),
                   mgm-service      (44),
                   subgrid-conn     (45),
                   network-capacity (46),
                   reporting        (47),
                   dns-cache-acceleration        (48),
                   ospf6            (49),
                   swap-usage       (50),
                   discovery-consolidator        (51),
                   discovery-collector           (52),
                   discovery-capacity            (53),
                   threat-protection             (54),
                   cloud-api                     (55),
                   threat-insight                (56),
                   taxii                         (57),
                   bfd                           (58),
                   outbound                      (59)
                 }

ibMemberServiceStatusTable OBJECT-TYPE
   SYNTAX SEQUENCE OF IbMemberServiceStatusEntry
   MAX-ACCESS    not-accessible
   STATUS        current
   DESCRIPTION   "A table of member service status."
   ::= { ibPlatformModule 9 }

ibMemberServiceStatusEntry OBJECT-TYPE
   SYNTAX        IbMemberServiceStatusEntry
   MAX-ACCESS    not-accessible
   STATUS        current
   DESCRIPTION   "A conceptual row containing info about a particular
                  service status."
   INDEX         {ibServiceName}
   ::= { ibMemberServiceStatusTable 1 }

IbMemberServiceStatusEntry ::=
   SEQUENCE {
     ibServiceName                IbServiceNames,
     ibServiceStatus              IbServiceStates,
     ibServiceDesc                IbString
   }

ibServiceName OBJECT-TYPE
   SYNTAX        IbServiceNames
   MAX-ACCESS    read-only
   STATUS        current
   DESCRIPTION   "Service Name."
   ::= { ibMemberServiceStatusEntry 1 }

ibServiceStatus OBJECT-TYPE
   SYNTAX        IbServiceStates
   MAX-ACCESS    read-only
   STATUS        current
   DESCRIPTION   "Service Status."
   ::= { ibMemberServiceStatusEntry 2 }

ibServiceDesc OBJECT-TYPE
   SYNTAX        IbString
   MAX-ACCESS    read-only
   STATUS        current
   DESCRIPTION   "Service Description."
   ::= { ibMemberServiceStatusEntry 3 }

ibMemberNodeServiceStatusTable OBJECT-TYPE
   SYNTAX SEQUENCE OF IbMemberNodeServiceStatusEntry
   MAX-ACCESS    not-accessible
   STATUS        current
   DESCRIPTION   "A table of Physical Node's Service Status."
   ::= { ibPlatformModule 10 }

ibMemberNodeServiceStatusEntry OBJECT-TYPE
   SYNTAX        IbMemberNodeServiceStatusEntry
   MAX-ACCESS    not-accessible
   STATUS        current
   DESCRIPTION   "A conceptual row containing info about a particular
                  service status."
   INDEX         {ibNodeServiceName}
   ::= { ibMemberNodeServiceStatusTable 1 }

IbMemberNodeServiceStatusEntry ::=
   SEQUENCE {
     ibNodeServiceName                IbServiceNames,
     ibNodeServiceStatus              IbServiceStates,
     ibNodeServiceDesc                IbString
   }

ibNodeServiceName OBJECT-TYPE
   SYNTAX        IbServiceNames
   MAX-ACCESS    read-only
   STATUS        current
   DESCRIPTION   "Service Name."
   ::= { ibMemberNodeServiceStatusEntry 1 }

ibNodeServiceStatus OBJECT-TYPE
   SYNTAX        IbServiceStates
   MAX-ACCESS    read-only
   STATUS        current
   DESCRIPTION   "Service Status."
   ::= { ibMemberNodeServiceStatusEntry 2 }

ibNodeServiceDesc OBJECT-TYPE
   SYNTAX        IbString
   MAX-ACCESS    read-only
   STATUS        current
   DESCRIPTION   "Service Description."
   ::= { ibMemberNodeServiceStatusEntry 3 }

ibMemberPassiveNodeServiceStatusTable OBJECT-TYPE
   SYNTAX SEQUENCE OF IbMemberPassiveNodeServiceStatusEntry
   MAX-ACCESS    not-accessible
   STATUS        current
   DESCRIPTION   "A table of Physical Node's Service Status."
   ::= { ibPlatformModule 11 }

ibMemberPassiveNodeServiceStatusEntry OBJECT-TYPE
   SYNTAX        IbMemberPassiveNodeServiceStatusEntry
   MAX-ACCESS    not-accessible
   STATUS        current
   DESCRIPTION   "A conceptual row containing info about a particular
                  service status."
   INDEX         {ibPassiveNodeServiceName}
   ::= { ibMemberPassiveNodeServiceStatusTable 1 }

IbMemberPassiveNodeServiceStatusEntry ::=
   SEQUENCE {
     ibPassiveNodeServiceName                IbServiceNames,
     ibPassiveNodeServiceStatus              IbServiceStates,
     ibPassiveNodeServiceDesc                IbString
   }

ibPassiveNodeServiceName OBJECT-TYPE
   SYNTAX        IbServiceNames
   MAX-ACCESS    read-only
   STATUS        current
   DESCRIPTION   "Service Name."
   ::= { ibMemberPassiveNodeServiceStatusEntry 1 }

ibPassiveNodeServiceStatus OBJECT-TYPE
   SYNTAX        IbServiceStates
   MAX-ACCESS    read-only
   STATUS        current
   DESCRIPTION   "Service Status."
   ::= { ibMemberPassiveNodeServiceStatusEntry 2 }

ibPassiveNodeServiceDesc OBJECT-TYPE
   SYNTAX        IbString
   MAX-ACCESS    read-only
   STATUS        current
   DESCRIPTION   "Service Description."
   ::= { ibMemberPassiveNodeServiceStatusEntry 3 }

ibGridStatus  OBJECT-TYPE
   SYNTAX         IbString
   MAX-ACCESS     read-only
   STATUS         current
   DESCRIPTION "Grid Status"
   ::= { ibPlatformModule 12 }

ibHaStatus  OBJECT-TYPE
   SYNTAX         IbString
   MAX-ACCESS     read-only
   STATUS         current
   DESCRIPTION "High Availability Status"
   ::= { ibPlatformModule 13 }

ibGridMasterCandStatus  OBJECT-TYPE
   SYNTAX         IbString
   MAX-ACCESS     read-only
   STATUS         current
   DESCRIPTION "Grid Master candidate status"
   ::= { ibPlatformModule 14 }

ibGridMasterVIP  OBJECT-TYPE
   SYNTAX         IbString
   MAX-ACCESS     read-only
   STATUS         current
   DESCRIPTION "Grid Master virtual IP address"
   ::= { ibPlatformModule 15 }

ibGridReplicationState  OBJECT-TYPE
   SYNTAX         IbString
   MAX-ACCESS     read-only
   STATUS         current
   DESCRIPTION "Grid Replication State"
   ::= { ibPlatformModule 16 }

ibCPU1Temperature  OBJECT-TYPE
   SYNTAX         IbFloat 
   MAX-ACCESS     read-only
   STATUS         current
   DESCRIPTION "Infoblox CPU One temperature."
   ::= { ibPlatformModule 17 }

ibCPU2Temperature  OBJECT-TYPE
   SYNTAX         IbFloat 
   MAX-ACCESS     read-only
   STATUS         current
   DESCRIPTION "Infoblox CPU Two temperature."
   ::= { ibPlatformModule 18 }

IbSnicNames ::= TEXTUAL-CONVENTION
   STATUS        current
   DESCRIPTION   "It defines the names for SNIC supported interfaces."
   SYNTAX        INTEGER {
                   lan1             (1),
                   lan2             (2),
                   ha               (3)
                 }

ibSystemMonitorSnicStatsTable1 OBJECT-TYPE
   SYNTAX SEQUENCE OF IbSystemMonitorSnicStatsEntry1
   MAX-ACCESS    not-accessible
   STATUS        current
   DESCRIPTION   "A table of SNIC statistics during last 1 min."
   ::= { ibSystemMonitorSnic 1 }

ibSystemMonitorSnicStatsEntry1 OBJECT-TYPE
   SYNTAX        IbSystemMonitorSnicStatsEntry1
   MAX-ACCESS    not-accessible
   STATUS        current
   DESCRIPTION   "A conceptual row containing info about a particular
                  SNIC statistics."
   INDEX         { ibSnicName1 }
   ::= { ibSystemMonitorSnicStatsTable1 1 }

IbSystemMonitorSnicStatsEntry1 ::=
   SEQUENCE {
     ibSnicName1                   IbSnicNames,
     ibSnicRxBits1                 INTEGER,
     ibSnicRxPackets1              INTEGER,
     ibSnicTxBits1                 INTEGER,
     ibSnicTxPackets1              INTEGER,
     ibSnicDropBits1               INTEGER,
     ibSnicDropPackets1            INTEGER
   }

ibSnicName1 OBJECT-TYPE
   SYNTAX        IbSnicNames
   MAX-ACCESS    read-only
   STATUS        current
   DESCRIPTION   "SmartNic Name."
   ::= { ibSystemMonitorSnicStatsEntry1 1 }

ibSnicRxBits1 OBJECT-TYPE
   SYNTAX        INTEGER
   MAX-ACCESS    read-only
   STATUS        current
   DESCRIPTION   "SmartNic recieved bits per second."
   ::= { ibSystemMonitorSnicStatsEntry1 2 }

ibSnicRxPackets1 OBJECT-TYPE
   SYNTAX        INTEGER
   MAX-ACCESS    read-only
   STATUS        current
   DESCRIPTION   "SmartNic recieved packets per second."
   ::= { ibSystemMonitorSnicStatsEntry1 3 }

ibSnicTxBits1 OBJECT-TYPE
   SYNTAX        INTEGER
   MAX-ACCESS    read-only
   STATUS        current
   DESCRIPTION   "SmartNic sent bits per second."
   ::= { ibSystemMonitorSnicStatsEntry1 4 }

ibSnicTxPackets1 OBJECT-TYPE
   SYNTAX        INTEGER
   MAX-ACCESS    read-only
   STATUS        current
   DESCRIPTION   "SmartNic sent packets per second."
   ::= { ibSystemMonitorSnicStatsEntry1 5 }

ibSnicDropBits1 OBJECT-TYPE
   SYNTAX        INTEGER
   MAX-ACCESS    read-only
   STATUS        current
   DESCRIPTION   "SmartNic dropped bits per second."
   ::= { ibSystemMonitorSnicStatsEntry1 6 }

ibSnicDropPackets1 OBJECT-TYPE
   SYNTAX        INTEGER
   MAX-ACCESS    read-only
   STATUS        current
   DESCRIPTION   "SmartNic dropped packets per second."
   ::= { ibSystemMonitorSnicStatsEntry1 7 }



ibSystemMonitorSnicStatsTable5 OBJECT-TYPE
   SYNTAX SEQUENCE OF IbSystemMonitorSnicStatsEntry5
   MAX-ACCESS    not-accessible
   STATUS        current
   DESCRIPTION   "A table of SNIC statistics during last 5 min."
   ::= { ibSystemMonitorSnic 2 }

ibSystemMonitorSnicStatsEntry5 OBJECT-TYPE
   SYNTAX        IbSystemMonitorSnicStatsEntry5
   MAX-ACCESS    not-accessible
   STATUS        current
   DESCRIPTION   "A conceptual row containing info about a particular
                  SNIC statistics."
   INDEX         { ibSnicName5 }
   ::= { ibSystemMonitorSnicStatsTable5 1 }

IbSystemMonitorSnicStatsEntry5 ::=
   SEQUENCE {
     ibSnicName5                   IbSnicNames,
     ibSnicRxBits5                 INTEGER,
     ibSnicRxPackets5              INTEGER,
     ibSnicTxBits5                 INTEGER,
     ibSnicTxPackets5              INTEGER,
     ibSnicDropBits5               INTEGER,
     ibSnicDropPackets5            INTEGER
   }

ibSnicName5 OBJECT-TYPE
   SYNTAX        IbSnicNames
   MAX-ACCESS    read-only
   STATUS        current
   DESCRIPTION   "SmartNic Name."
   ::= { ibSystemMonitorSnicStatsEntry5 1 }

ibSnicRxBits5 OBJECT-TYPE
   SYNTAX        INTEGER
   MAX-ACCESS    read-only
   STATUS        current
   DESCRIPTION   "SmartNic recieved bits per second."
   ::= { ibSystemMonitorSnicStatsEntry5 2 }

ibSnicRxPackets5 OBJECT-TYPE
   SYNTAX        INTEGER
   MAX-ACCESS    read-only
   STATUS        current
   DESCRIPTION   "SmartNic recieved packets per second."
   ::= { ibSystemMonitorSnicStatsEntry5 3 }

ibSnicTxBits5 OBJECT-TYPE
   SYNTAX        INTEGER
   MAX-ACCESS    read-only
   STATUS        current
   DESCRIPTION   "SmartNic sent bits per second."
   ::= { ibSystemMonitorSnicStatsEntry5 4 }

ibSnicTxPackets5 OBJECT-TYPE
   SYNTAX        INTEGER
   MAX-ACCESS    read-only
   STATUS        current
   DESCRIPTION   "SmartNic sent packets per second."
   ::= { ibSystemMonitorSnicStatsEntry5 5 }

ibSnicDropBits5 OBJECT-TYPE
   SYNTAX        INTEGER
   MAX-ACCESS    read-only
   STATUS        current
   DESCRIPTION   "SmartNic dropped bits per second."
   ::= { ibSystemMonitorSnicStatsEntry5 6 }

ibSnicDropPackets5 OBJECT-TYPE
   SYNTAX        INTEGER
   MAX-ACCESS    read-only
   STATUS        current
   DESCRIPTION   "SmartNic dropped packets per second."
   ::= { ibSystemMonitorSnicStatsEntry5 7 }

ibSystemMonitorSnicCpuCoreUtiliz OBJECT-TYPE
   SYNTAX SEQUENCE OF IbSystemMonitorSnicCpuCoreUtilizEntry
   MAX-ACCESS    not-accessible
   STATUS        current
   DESCRIPTION   "A table of SNIC cpu core utilization during last 1 min."
   ::= { ibSystemMonitorSnic 3 }

ibSystemMonitorSnicCpuCoreUtilizEntry OBJECT-TYPE
   SYNTAX        IbSystemMonitorSnicCpuCoreUtilizEntry
   MAX-ACCESS    not-accessible
   STATUS        current
   DESCRIPTION   "A conceptual row containing info about a particular
                  SNIC cpu core utilization on the card."
   INDEX         { ibSnicCoreName }
   ::= { ibSystemMonitorSnicCpuCoreUtiliz 1 }

IbSystemMonitorSnicCpuCoreUtilizEntry ::=
   SEQUENCE {
     ibSnicCoreName               IbString,
     ibSnicCoreCountIndex         INTEGER,
     ibSnicCoreUtilz              IbString
   }

ibSnicCoreName OBJECT-TYPE
   SYNTAX        IbString
   MAX-ACCESS    read-only
   STATUS        current
   DESCRIPTION   "SmartNic Core Name."
   ::= { ibSystemMonitorSnicCpuCoreUtilizEntry 1 }

ibSnicCoreCountIndex OBJECT-TYPE
   SYNTAX        INTEGER
   MAX-ACCESS    read-only
   STATUS        current
   DESCRIPTION   "SmartNic Core Count index."
   ::= { ibSystemMonitorSnicCpuCoreUtilizEntry 2 }

ibSnicCoreUtilz OBJECT-TYPE
   SYNTAX        IbString
   MAX-ACCESS    read-only
   STATUS        current
   DESCRIPTION   "SmartNic CPU Core utilisation"
   ::= { ibSystemMonitorSnicCpuCoreUtilizEntry 3 }
END
